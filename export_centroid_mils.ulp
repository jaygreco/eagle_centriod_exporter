#usage "Create Centroid file for automated assembly, units in mils<p>"

string Version = "1.0"; 
string fileMessage;

string rotation(real Angle)
{
  string s;
  sprintf(s, "%.1f", Angle);
  int pos = strchr(s, '.');
  if (pos >= 0) if (s[pos + 1] == '0') s[pos] = 0;
  return s;
}

string side(int Mirror)
{
  string s;

  if (Mirror){
    s = "Bottom";
  }
  else {
    s = "Top";
  }
  return s;
}

if (!board) {
   dlgMessageBox("<hr><b>ERROR: This ULP will only operate in the board layout view.</b></hr><p>Switch to the board layout editor and re-run.");
   exit(1);
}

if (board) board(B) {
   output(filesetext(B.name, "_centroid_mils.csv")) {
     printf("SMD component position file.\n");
     printf("Created by export_centroid.ulp %s.\n\n", Version);
     printf("Centroid Data for pc board: \"%s\" as of: %s\n", filename(B.name), t2string(time()));
     printf("Measurements are in mils. Comma delimited\n");
     printf("Only surface mount components included\n\n");
     printf("%s,%s,%s,%s,%s\n", "RefDes", "Layer", "LocationX", "LocationY", "Rotation");
     B.elements(E) {
       int isSmd;
       isSmd = 0;
       int isDNP;
       isDNP = 0;
       E.package.contacts(C) { if (C.smd) isSmd = 1; }
       E.attributes(A) {
        if (A.name == "BOM_DNP" && A.value == "DNP") {isDNP = 1;}
       }
       if (isSmd && !isDNP) printf("%s,%s,%5.3f,%5.3f,%s\n", E.name, side(E.mirror), u2mil(E.x), u2mil(E.y), rotation(E.angle));
       }
     }

	fileMessage = "<hr><b>Centroid file for automated PCB assembly generated!</b></hr><p>Include this file in the .ZIP file along with your GERBER files and Bill of Materials:<P>" + filesetext(B.name, "_centroid_mils.csv\n");

	dlgMessageBox(fileMessage);
}
